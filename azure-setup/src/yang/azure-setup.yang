module azure-setup {

  namespace "http://example.com/azure-setup";
  prefix azure-setup;

  import ietf-inet-types {
    prefix inet;
  }
  import tailf-common {
    prefix tailf;
  }
  import tailf-ncs {
    prefix ncs;
  }

  description
    "provisioning config for microsoft azure:
    This service uses a template to configure an IPSec VPN tunnel connecting your local device with the Azure gateway.
    ";

  revision 2016-01-01 {
    description
      "Initial revision.";
  }

  list azure-setup {
    description "demo azure config service";

    key name;
    leaf name {
      tailf:info "Unique service id";
      tailf:cli-allow-range;
      type string;
    }

    uses ncs:service-data;
    ncs:servicepoint "demo-template";

    
    leaf-list device { 
      tailf:info "local device";
      type leafref {
        path "/ncs:devices/ncs:device/ncs:name";
      }
    }

    leaf azure-ip {
      mandatory true;
      tailf:info "azure gateway ip";
      type string;
}
    leaf psk {
      mandatory true;
      tailf:info "pre shared key for secure connection with gateway";
      type string;
    }
    leaf out-ip {
      mandatory true;
      tailf:info "public ip of outgoing interface";
      type string;
    }
     

}
}
